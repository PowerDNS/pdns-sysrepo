/*
 * Copyright 2019-2020 Pieter Lexis <pieter.lexis@powerdns.com>
 *
 * Licensed under the Apache License, Version 2.0 (the "License");
 * you may not use this file except in compliance with the License.
 * You may obtain a copy of the License at
 *
 * http://www.apache.org/licenses/LICENSE-2.0
 *
 * Unless required by applicable law or agreed to in writing, software
 * distributed under the License is distributed on an "AS IS" BASIS,
 * WITHOUT WARRANTIES OR CONDITIONS OF ANY KIND, either express or implied.
 * See the License for the specific language governing permissions and
 * limitations under the License.";
 */

module pdns-server-typedef-test {
    yang-version 1.1;
    namespace "http://powerdns.com/yang/pdns-server-test";
    prefix pdns-server-typedef-test;

    import pdns-server {
        prefix "pdns-server";
    }


    organization
      "PowerDNS.COM BV";
    contact
      "Pieter Lexis <mailto:pieter.lexis@powerdns.com>";

    description
      "This module is only used for testing the typedefs in pdns-server";

    revision 2020-01-23 {
      description "initial";
    }

    container hostnames {
        leaf-list hostname {
            type pdns-server:host-name;
        }
    }

    container zonenames {
        leaf-list zonename {
            type pdns-server:zone-name;
        }
    }

    container ownernames {
        leaf-list owner-name {
            type pdns-server:owner-name;
        }
    }
}
