/*
 * Copyright 2019-2020 Pieter Lexis <pieter.lexis@powerdns.com>
 *
 * Licensed under the Apache License, Version 2.0 (the "License");
 * you may not use this file except in compliance with the License.
 * You may obtain a copy of the License at
 *
 * http://www.apache.org/licenses/LICENSE-2.0
 *
 * Unless required by applicable law or agreed to in writing, software
 * distributed under the License is distributed on an "AS IS" BASIS,
 * WITHOUT WARRANTIES OR CONDITIONS OF ANY KIND, either express or implied.
 * See the License for the specific language governing permissions and
 * limitations under the License.";
 */

/*
 * Links:
 *  https://github.com/CZ-NIC/yang-dns
 *  https://github.com/YangModels/yang/tree/master/standard/ietf/RFC
 */
module pdns-server {
    yang-version 1.1;
    namespace "http://powerdns.com/yang/pdns-server";
    prefix pdns-server;

    import ietf-inet-types {
        prefix inet;
        revision-date 2013-07-15;
    }

    import iana-dns-class-rr-type {
        prefix dnsct;
    }

    import dns-zone-common {
        prefix dnszc;
    }

    organization
      "PowerDNS.COM BV";
    contact
      "Pieter Lexis <mailto:pieter.lexis@powerdns.com>";

    description
      "This module describes the PowerDNS Authoritative Server";

    revision 2020-04-16 {
      description "Add SRV record and update namespace to a non-ietf one";
    }

    revision 2020-02-13 {
      description "Add option to not restart te PowerDNS service";
    }

    revision 2020-02-06 {
      description "Add DNAME to supported rrset types";
    }

    revision 2020-01-23 {
      description
      "* Stop accepting dns names without a trailing dot
       * Add the possibility for wildcard RRs";
    }

    revision 2020-01-20 {
      description "Add a rrset-state container for slave zones";
    }

    revision 2020-01-17 {
      description "Allows more than one piece of rdata for types that support it.";
    }

    revision 2020-01-14 {
      description
            "
           Several new features:
           
            * Added also-notify global option and as per-zone setting
            * Added allow-axfr as a per-zone setting
            ";
    }

    revision 2020-01-06 {
        description
          "Add pdns-sysrepo configuration";
    }

    revision 2019-12-13 {
        description
          "Add RRSet configuration, hidden behind an rrset-management feature flag";
    }

    revision 2019-12-10 {
        description
          "Add allow-axfr ACL option";
    }

    revision 2019-12-04 {
        description
          "Add the LMDB backend as a configuration option";
    }

    revision 2019-11-19 {
        description
          "Added Zone config, Zone operational status and webserver settings";
    }

    revision 2019-11-08 {
        description
          "Added backends and config";
    }

    revision 2019-10-25 {
        description
          "Initial revision, not for public consumption yet";
    }

    feature rrset-management {
      description "Enable to allow updating RRSets in the YANG datastore";
    }

    typedef backendtype {
        type enumeration {
            enum "gsqlite3";
            enum "lmdb";
        /*
         * enum "gmysql";
         * enum "gpgsql";
         */
        }
    }

    typedef sqlite3-journal-mode {
        description
          "Possible PRAGMA values for the sqlite3 journal mode setting";

        type enumeration {
            enum "DELETE";
            enum "MEMORY";
            enum "OFF";
            enum "PERSIST";
            enum "TRUNCATE";
            enum "WAL";
        }
    }

    typedef sqlite3-synchronous-mode {
        type enumeration {
            enum "0"; // OFF
            enum "OFF";
            enum "1"; // NORMAL
            enum "NORMAL";
            enum "2"; // FULL
            enum "FULL";
            enum "3"; // EXTRA
            enum "EXTRA";
        }
    }

    typedef lmdb-sync-mode {
        description
          "Synchronisation mode for the on-disk database";

        type enumeration {
            enum "sync";
            enum "nosync";
            enum "nometasync";
            enum "mapasync";
        }
    }

    typedef lmdb-shards {
        type uint32;
    }

    typedef zonetype {
        type enumeration {
            enum "master";
            enum "slave";
            enum "native";
        }
    }

    typedef acl-ref {
        type leafref {
            path "/pdns-server:axfr-access-control-list/pdns-server:name";
        }
        description
          "This type is used for referring to a configured access control
           list.";
    }

    typedef notify-ref {
      type leafref {
        path "/pdns-server:notify-endpoint/pdns-server:name";
      }
      description "This type is used to reference configured notify endpoints";
    }

    typedef owner-name {
        // TODO support IDN (xn--XX-XXXX)
        // TODO support symbols other than - and _
        description
          "The owner name must be a valid dns name for the owner of a resource record.
           It can start with a '*' to denote a wildcard and must end with a '.'";

        type string {
            length "1..255";
            pattern '(\*\.)?([a-z0-9_][-a-z0-9_]{0,61}[a-z0-9]\.)+|\.';
            pattern ".*--.*" {
              modifier invert-match;
            }
        }
    }

    typedef zone-name {
      type owner-name {
        pattern '([a-z0-9_][-a-z0-9_]{0,63}\.)+|\.';
      }
    }

    typedef host-name {
      type zone-name {
        pattern '([a-z0-9]([-a-z0-9_]{0,61}[a-z0-9])\.){2,}';
      }
    }

    typedef master-ref {
      type leafref {
        path "/pdns-server:master-endpoint/pdns-server:name";
      }
      description "This type is used to reference master servers";
    }

    /*
     * Groupings
     */
    grouping endpoint {
        description
          "An IP endpoint, including the port";
        leaf ip-address {
            type inet:ip-address;
            mandatory true;
        }
        leaf port {
            type inet:port-number;
        }
    }

    grouping backend {
        description
          "The configuration of a PowerDNS backend";
        leaf backendtype { // TODO figure out a better name!
            type backendtype;
        }

        leaf database {
            description
              "Name or location of the database";
            type string;
            when "../backendtype = 'gsqlite3'";
        }

        leaf pragma-journal-mode {
            description
              "SQLite3 journal mode to set";
            type sqlite3-journal-mode;
            default "WAL";
            when "../backendtype = 'gsqlite3'";
        }

        leaf pragma-synchronous {
            description
              "Set this to OFF for blazing speed";
            type sqlite3-synchronous-mode;
            default "NORMAL";
            when "../backendtype = 'gsqlite3'";
        }

        leaf pragma-foreign-keys {
            description
              "Enable foreign key constraints";
            type boolean;
            default false;
            when "../backendtype = 'gsqlite3'";
        }

        leaf shards {
            description
              "Records database will be split into this number of shards";
            type lmdb-shards;
            default 64;
            when "../backendtype = 'lmdb'";
        }

        leaf sync-mode {
            type lmdb-sync-mode;
            default "mapasync";
            when "../backendtype = 'lmdb'";
        }

        leaf filename {
            description
              "Path to the LMDB file";
            type string;
            mandatory true;
            when "../backendtype = 'lmdb'";
        }

        leaf dnssec {
            description
              "Enable DNSSEC support in this backend";
            type boolean;
            default false;
            when "../backendtype = 'gsqlite3'";
        }
    }

    grouping rdata {
        container SOA {
            when "../../type='SOA'";
            description
              "RDATA content for 'SOA' Resource Record.";
            leaf mname {
                type dnszc:domain-name;
                mandatory "true";
                description
                  "Name server that was the original or primary source of
                   data for this zone.";
            }
            leaf rname {
                type dnszc:domain-name;
                mandatory "true";
                description
                  "Mailbox of the person responsible for this zone.";
            }
            leaf serial {
                type uint32;
                mandatory "true";
                description
                  "Version number of the original copy of the zone.";
            }
            leaf refresh {
                type dnszc:time-interval;
                mandatory "true";
                description
                  "Time interval that should elapse before the zone should
                   be refreshed.";
            }
            leaf retry {
                type dnszc:time-interval;
                mandatory "true";
                description
                  "Time interval that should elapse before a failed refresh
                   should be retried.";
            }
            leaf expire {
                type dnszc:time-interval;
                mandatory "true";
                description
                  "Upper limit on the time interval that can elapse before
                   the zone is no longer authoritative.";
            }
            leaf minimum {
                type dnszc:time-interval;
                mandatory "true";
                description
                  "Minimum TTL that should be exported with any RR from
                   this zone.";
            }
        }
        container A {
            when "../../type = 'A'";
            description
              "RDATA content for 'A' Resource Record.";
            reference
              "RFC 1035: Domain Names - Implementation and
               Specification.";
            leaf-list address {
                min-elements 1;
                type inet:ipv4-address-no-zone;
                description
                  "IPv4 address.";
            }
        }
        container CNAME {
            when "../../type = 'CNAME'";
            description
              "RDATA content for 'CNAME' Resource Record.";
            reference
              "RFC 1035: Domain Names - Implementation and
               Specification.";
            leaf cname {
                type inet:domain-name;
                mandatory "true";
                description
                  "Canonical or primary name for the owner.";
            }
        }
        container MX {
            when "../../type = 'MX'";
            description
              "RDATA content for 'MX' Resource Record.";
            reference
              "RFC 1035: Domain Names - Implementation and
               Specification.";
            list mail-exchanger {
                key "preference exchange";
                leaf preference {
                    type uint16;
                    mandatory "true";
                    description
                      "Preference given to this RR among others at the same
                       owner. Lower values are preferred.";
                }
                leaf exchange {
                    type inet:domain-name;
                    mandatory "true";
                    description
                      "Host willing to act as a mail exchange for the owner
                       name.";
                }
            }
        }
        container NS {
            when "../../type = 'NS'";
            description
              "RDATA content for 'NS' Resource Record.";
            reference
              "RFC 1035: Domain Names - Implementation and
               Specification.";
            leaf-list nsdname {
                type inet:domain-name;
                min-elements 1;
                description
                  "Host which should be authoritative for the specified
                   domain.";
            }
        }
        container PTR {
            when "../../type = 'PTR'";
            description
              "RDATA content for 'PTR' Resource Record.";
            reference
              "RFC 1035: Domain Names - Implementation and
               Specification.";
            leaf-list ptrdname {
                type inet:domain-name;
                min-elements 1;
                description
                  "A pointer to some location in the domain name space.";
            }
        }
        container TXT {
            when "../../type = 'TXT'";
            description
              "RDATA content for 'TXT' Resource Record.";
            reference
              "RFC 1035: Domain Names - Implementation and
               Specification.";
            leaf-list txt-data {
                type dnszc:ascii-string;
                min-elements 1;
                description
                  "Descriptive text whose semantics depends on the domain
                   where it is found.";
            }
        }
        container AAAA {
            when "../../type = 'AAAA'";
            description
              "RDATA content for 'AAAA' Resource Record.";
            reference
              "RFC 3596: DNS Extensions to Support IP Version 6";
            leaf-list address {
                type inet:ipv6-address-no-zone;
                min-elements 1;
                description
                  "IPv6 address.";
            }
        }
        container SRV {
          when "../../type = 'SRV'";
          description
            "RDATA for 'SRV' Resource Record";
          reference
            "RFC 2782: A DNS RR for specifying the location of services (DNS SRV)";
          list service {
            key "priority weight port target";
            leaf priority {
              type uint16;
              description "The priority of this target host";
            }
            leaf weight {
              type uint16;
              description "A server selection mechanism. The weight field specifies a relative weight for entries with the same priority";
            }
            leaf port {
              type inet:port-number;
              description "The port on this target host of this service";
            }
            leaf target {
              type host-name;
              description "The domain name of the target host.";
            }
          }
        }
        container DNAME {
            when "../../type = 'DNAME'";
            description
              "RDATA content for 'DNAME' Resource Record.";
            reference
              "RFC 2672: Non-Terminal DNS Name Redirection";
            leaf target {
                type dnszc:domain-name;
                mandatory "true";
                description
                  "Target domain name that is substituted for 'owner' as a
                   suffix of a domain name.";
            }
        }
    }

    grouping rrset {
        // Nearly a straight up copy from
        // https://gitlab.labs.nic.cz/jetconf/jetconf-knot/blob/master/yang-modules/dns-zones-state@2017-01-12.yang
        // RRSIG data is removed
        description
          "RRSet";
        uses dnszc:owner-field;

        leaf ttl {
            type dnszc:time-interval;
            mandatory "true";
            description
              "Time-To-Live of the RR.";
        }

        leaf type {
            type dnsct:rr-type;
        }

        container rdata {
            uses rdata;
        }

    }

    grouping zone {
        description
          "A DNS Zone";
        leaf name {
            description
              "Name of the zone, MUST be suffixed with a dot";
            type zone-name;
            mandatory true;
        }

        leaf class {
            type dnsct:dns-class;
        }
        leaf zonetype {
            type zonetype;
        }

        leaf-list masters {
            description
              "Master servers for this zone";
            type master-ref;
            when "../zonetype = 'slave'";
            min-elements 1;
        }

        leaf-list also-notify {
          if-feature "rrset-management";
          when "../zonetype = 'master'";
          description
            "List of remote endpoints to send NOTIFY packets";
          type notify-ref;
        }

        leaf-list allow-axfr {
          if-feature "rrset-management";
          when "../zonetype = 'master' or ../zonetype = 'native'";
          description
            "Access Control Lists applied for this zone.";
          type acl-ref;
        }

        list rrset {
            if-feature "rrset-management";
            when "../zonetype = 'master' or ../zonetype = 'native'";
            uses rrset;
            key "owner type";
        }

        list rrset-state {
            config false;
            if-feature "rrset-management";
            when "../zonetype = 'slave'";
            uses rrset;
            key "owner type";
        }
    }

    grouping webserver {
        description
          "Webserver configuration";
        leaf address {
            type inet:ip-address;
        }
        leaf port {
            type inet:port-number;
        }
        leaf password {
            description
              "Password required to access the non-API webserver paths";
            type string;
        }
        leaf api-key {
            description
              "Pre-shared API key. Set this to enable the API";
            type string;
        }
        leaf-list allow-from {
            description
              "ACL for the webserver";
            type inet:ip-prefix;
        }
        leaf max-body-size {
            description
              "Maximum size of the response sent by the webserver in megabytes";
            type uint32;
        }
        leaf loglevel {
            description
              "How munch the webserver should log";
            type enumeration {
                enum "none";
                enum "normal";
                enum "detailed";
            }
        }
    }

    grouping pdns-sysrepo {
      container pdns-service {
        leaf name {
          description
                  "The name of the PowerDNS Systemd service";
          type string {
            pattern
                      "[-a-zA-Z0-9_@]+.service";
          }
        }
        leaf config-file {
          type string; // TODO use a filepath-style type
        }
        leaf restart {
          type boolean;
          default true;
          description
                  "Restart the PowerDNS Authoritative Server service when the configuration in
                   /pdns-server:pdns-server/ or /pdns-server:pdns-sysrepo/service is changed";
        }
      }

      container logging {
        leaf level {
          description "The amount of logging to do";
          type enumeration {
            enum "off";
            enum "critical";
            enum "error";
            enum "warning";
            enum "info";
            enum "debug";
            enum "trace";
          }
        }
        leaf timestamp {
          description "Whether to timestamp the logs";
          type boolean;
        }
      }
    }

    /*
     * Configuration data
     */
    list axfr-access-control-list {
        key "name";
        description
          "Access control lists.";
        leaf name {
            type string;
        }
        list network {
            key "name";
            unique "ip-prefix";
            description
              "Identification of a network.";
            leaf name {
                type string;
            }
            leaf ip-prefix {
                type inet:ip-prefix;
                mandatory "true";
                description
                  "IPv4 or IPv6 prefix in the usual ADDRESS/LENGTH
                   notation.";
            }
        }
    }

    list notify-endpoint {
      key "name";
      description
        "Endpoints that could be notified about zone updates";
      leaf name {
        type string;
      }
      list address {
        key "name";
        unique "ip-address port";

        description "Address to notify";
        leaf name {
          type string;
        }        

        uses endpoint {
          refine port {
            default 53;
          }
        }
      }
    }

    list master-endpoint {
      key "name";
      description
        "Endpoints that can act as a master for slave zones";
      leaf name {
        type string;
      }
      list address {
        key "name";
        unique "ip-address port";

        description "Address that are a master";
        leaf name {
          type string;
        }        

        uses endpoint {
          refine port {
            default 53;
          }
        }
      }
    }

    container pdns-server {
        description
          "Configuration of the PowerDNS Authoritative Server";
        list listen-addresses {
            description
              "The addresses this server is listening on for queries";
            key "name";
            unique "ip-address port";
            leaf name {
                type string;
            }
            uses endpoint {
                refine "port" {
                    default 53;
                }
            }
        }
        leaf master {
            description
              "Whether or not this service should act as a master.
               This means sending out NOTIFY messages to slave when zones are updated.";
            type boolean;
            default false;
        }
        leaf slave {
            description
              "Whether or not this service should act as a slave.
               This means checking zone validity and retrieving when out of date.";
            type boolean;
            default false;
        }

        leaf-list allow-axfr {
            description
              "Access Control Lists applied globally. Addresses in this list are always allowed to transfer all zones";
            type acl-ref;
        }

        leaf-list also-notify {
          description
            "List of remote endpoints to send NOTIFY packets for all master zones";
          type notify-ref;
        }

        container webserver {
            uses webserver {
                refine port {
                    default 8081;
                }
                refine address {
                    default "127.0.0.1";
                }
                refine allow-from {
                    default "127.0.0.0/8";
                }
            }
        }

        list backend {
            if-feature "not rrset-management";

            description
              "All backends that should be launched on startup, with their config";

            /*
             * As there's no 'default' backend... we can't enforce this
             * min-elements 1;
             */
            key "name";
            leaf name {
                type string;
            }
            uses backend;
        }
      }

    container pdns-sysrepo {
      uses pdns-sysrepo {
          refine pdns-service/name {
              default "pdns.service";
          }
          refine pdns-service/config-file {
              default "/etc/powerdns/pdns.conf";
          }
          refine logging/level {
              default "info";
          }
          refine logging/timestamp {
              default false;
          }
      }
    }

    container zones {
        list zones {
            description
              "All zones configured on this server";

            uses zone {
                refine class {
                    default "IN";
                }
            }
            key "name";
        }
    }

    container zones-state {
        if-feature "not rrset-management";
        
        config false;
        description
          "Operational state of zones";

        list zones {
            description
              "All zones configured on this server";

            uses zone;
            key "name";

            leaf serial {
                description
                  "The SOA serial for this zone";
                type uint32;
            }
        }
    }
}
